-- An EXPLICIT tag around a tagged CHOICE wraps the CHOICE's whole
-- encoding, its own tag included (X.680 §30.6, X.690 §8.14.3).
ExplicitTaggedChoiceTest DEFINITIONS EXPLICIT TAGS ::= BEGIN

Own ::= [5] CHOICE { b BOOLEAN, i INTEGER }

HoldsOwn ::= SEQUENCE {
    own    Own,
    tagged [4] Own,
    n      NULL
}

END
