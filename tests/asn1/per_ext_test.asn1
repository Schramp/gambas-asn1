PerExtTest DEFINITIONS AUTOMATIC TAGS ::= BEGIN

-- SEQUENCE with extension members.
-- Root: id (0..255), flag BOOLEAN.
-- Extension: note VisibleString OPTIONAL, extra INTEGER (0..255) OPTIONAL.
SeqWithExt ::= SEQUENCE {
    id    INTEGER (0..255),
    flag  BOOLEAN,
    ...,
    note  VisibleString (SIZE (1..8)) OPTIONAL,
    extra INTEGER (0..255) OPTIONAL
}

-- CHOICE with an extension alternative.
ChoiceWithExt ::= CHOICE {
    num  INTEGER (0..255),
    flag BOOLEAN,
    ...,
    str  VisibleString (SIZE (1..8))
}

-- Nested SEQUENCE used as an extension member in SeqDeepExt.
InnerSeq ::= SEQUENCE {
    a INTEGER (0..255),
    b BOOLEAN,
    c INTEGER (0..255)
}

-- SEQUENCE with an extension member that is itself a SEQUENCE (2 levels deep).
-- Used to test that receivers without knowledge of the extension skip the
-- entire open-type payload (which contains a PER-encoded InnerSeq).
SeqDeepExt ::= SEQUENCE {
    id   INTEGER (0..255),
    name VisibleString (SIZE (1..8)),
    ...,
    detail InnerSeq OPTIONAL
}

-- Same root layout as SeqDeepExt but with no known extension members.
-- Represents an old receiver that only knows about the root.
SeqDeepExtRootOnly ::= SEQUENCE {
    id   INTEGER (0..255),
    name VisibleString (SIZE (1..8)),
    ...
}

-- ENUMERATED with 70 extension items: the ordinals 64 and up take the
-- long form of the normally small non-negative whole number (X.691 §11.6.2).
BigExtEnum ::= ENUMERATED { r0, r1, ..., e0, e1, e2, e3, e4, e5, e6, e7, e8, e9, e10, e11, e12, e13, e14, e15, e16, e17, e18, e19, e20, e21, e22, e23, e24, e25, e26, e27, e28, e29, e30, e31, e32, e33, e34, e35, e36, e37, e38, e39, e40, e41, e42, e43, e44, e45, e46, e47, e48, e49, e50, e51, e52, e53, e54, e55, e56, e57, e58, e59, e60, e61, e62, e63, e64, e65, e66, e67, e68, e69 }

END
