-- Content past 2^24 bytes, the first length that needs 4 length octets
-- (X.690 §8.1.3.5). Used by tests/seq/test_long_length.cpp.
LongLengthTest DEFINITIONS ::= BEGIN

LongLen ::= SEQUENCE {
    n INTEGER,
    o OCTET STRING
}

END
