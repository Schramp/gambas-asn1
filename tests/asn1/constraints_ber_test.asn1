-- Java BER leg for inline member constraints (X.680 §51): each member,
-- alternative and element below carries its own constraint table, which
-- the cross-language table diff compares; BER bytes are unaffected.
ConstraintsBerTest DEFINITIONS ::= BEGIN

Limits ::= SEQUENCE {
    byte   INTEGER (0..255),
    neg    INTEGER (-5..5, ...),
    from   INTEGER (10..MAX),
    big    INTEGER (0..18446744073709551615),
    fixed  OCTET STRING (SIZE (4)),
    name   IA5String (SIZE (1..8)),
    bits   BIT STRING (SIZE (0..16)),
    opt    UTF8String (SIZE (2..MAX)) OPTIONAL,
    small  SEQUENCE OF INTEGER (0..9),
    sized  SEQUENCE (SIZE (1..3)) OF BOOLEAN
}

Pick ::= CHOICE {
    num  INTEGER (1..10),
    txt  VisibleString (SIZE (1..4))
}

Digits ::= SEQUENCE OF INTEGER (0..9)

END
