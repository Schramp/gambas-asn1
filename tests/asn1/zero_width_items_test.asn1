-- PER SEQUENCE OF/SET OF elements encoded in zero bits (NULL, X.691 §18;
-- an INTEGER with a single value, §11.1.3). Their count costs a few octets
-- of length determinant and the elements none, so a decoder refuses a list
-- counting more than its limit (200, as asn1c) once such an element shows
-- up. Elements of one bit or more, and many short lists, stay unlimited.

ZeroWidthItemsTest DEFINITIONS AUTOMATIC TAGS ::= BEGIN

    -- A NULL takes zero bits (X.691 §18): limited.
    Nulls ::= SEQUENCE OF NULL

    -- A single-value INTEGER takes zero bits too (§11.1.3): limited.
    Fives ::= SEQUENCE (SIZE(0..60000)) OF INTEGER (5..5)

    -- Control case: a BOOLEAN takes one bit (§12.1), so any count is
    -- backed by input: not limited.
    Flags ::= SEQUENCE OF BOOLEAN

    -- Control case: a nested list takes at least its length octet, so many
    -- short lists of NULLs are not limited.
    Rows ::= SEQUENCE OF Nulls

END
