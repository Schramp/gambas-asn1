-- gambas-asn1#466: real-codegen coverage for MemberDescriptor::validate —
-- an inline X.680 §51.4 FROM (PermittedAlphabet) constraint on a
-- character-string SEQUENCE member, combined with SIZE via
-- constraints::validate_char_string. `tag` covers the FROM-only case (no SIZE
-- clause at all). `Natural` has members of the kinds with a character set
-- of their own (X.680 §41) and no FROM: they are checked against that set.

RustAlphabetTest DEFINITIONS ::= BEGIN

    Code ::= SEQUENCE {
        digits NumericString (FROM ("0"|"1"|"2"|"3"|"4"|"5"|"6"|"7"|"8"|"9")) (SIZE(1..6)),
        tag    IA5String (FROM ("a"|"b"|"c"))
    }

    Natural ::= SEQUENCE {
        num   NumericString,
        print PrintableString (SIZE(1..8)),
        ia5   IA5String OPTIONAL,
        vis   VisibleString,
        utf8  UTF8String
    }

END
