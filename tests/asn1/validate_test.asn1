ValidateTest DEFINITIONS ::= BEGIN

  -- INTEGER: variety of bounds
  PercentInt   ::= INTEGER (0..100)         -- 0-low
  Tariff       ::= INTEGER (1000..2000)     -- positive non-zero low
  PositiveInt  ::= INTEGER (10..MAX)        -- semi-constrained
  SignedSmall  ::= INTEGER (-50..50)        -- symmetric signed
  NegRange     ::= INTEGER (-1000..-1)      -- negative-only
  WideUnsigned ::= INTEGER (5..1000000)     -- wider asymmetric

  -- OCTET STRING: varied SIZE bounds
  TinyBlob     ::= OCTET STRING (SIZE(2..4))    -- min 2
  MidBlob      ::= OCTET STRING (SIZE(5..12))   -- min 5
  FixedBlob    ::= OCTET STRING (SIZE(8))       -- exact 8

  -- BIT STRING: varied SIZE
  FlagsByte    ::= BIT STRING (SIZE(8))         -- exact byte
  FlagsRange   ::= BIT STRING (SIZE(16..24))    -- min 16

  -- Built-in alphabets + varied SIZE
  Code         ::= NumericString   (SIZE(3..6))
  Name         ::= PrintableString (SIZE(2..20))
  Token        ::= IA5String       (SIZE(4..10))
  Visi         ::= VisibleString   (SIZE(6..12))

  -- Reduced alphabets via FROM (codegen alphabet field is TODO; encoded via base
  -- type rules today — these definitions exist so the test surface stays in
  -- place when FROM-custom validation lands)
  HexDigit     ::= IA5String (FROM ("0"|"1"|"2"|"3"|"4"|"5"|"6"|"7"|"8"|"9"|"A"|"B"|"C"|"D"|"E"|"F")) (SIZE(1..8))
  YesNo        ::= IA5String (FROM ("Y"|"N")) (SIZE(1..3))
  Vowels       ::= PrintableString (FROM ("a"|"e"|"i"|"o"|"u")) (SIZE(1..5))

  -- Multi-byte storage: SIZE and FROM count characters, not bytes
  Umlauts      ::= UTF8String      (SIZE(1..4))
  Pair         ::= BMPString       (SIZE(1..2))
  Caps         ::= BMPString       (FROM ("A".."Z"))
  Quad         ::= UniversalString (SIZE(1..2))

  -- ENUMERATED
  Color        ::= ENUMERATED { red(0), green(1), blue(2) }

  -- SEQUENCE OF varied SIZE
  ShortList    ::= SEQUENCE (SIZE(1..3))  OF PercentInt
  MidList      ::= SEQUENCE (SIZE(2..8))  OF SignedSmall

  -- Semi-constrained unsigned (0..MAX) → uint64_t storage
  ByteCount    ::= INTEGER (0..MAX)

  -- Wrappers so each constraint type can be encoded standalone
  HasPct       ::= SEQUENCE { v PercentInt   }
  HasTariff    ::= SEQUENCE { v Tariff       }
  HasPos       ::= SEQUENCE { v PositiveInt  }
  HasSigned    ::= SEQUENCE { v SignedSmall  }
  HasNeg       ::= SEQUENCE { v NegRange     }
  HasWide      ::= SEQUENCE { v WideUnsigned }
  HasTiny      ::= SEQUENCE { v TinyBlob     }
  HasMid       ::= SEQUENCE { v MidBlob      }
  HasFixed     ::= SEQUENCE { v FixedBlob    }
  HasFlagsByte ::= SEQUENCE { v FlagsByte    }
  HasFlagsRange::= SEQUENCE { v FlagsRange   }
  HasCode      ::= SEQUENCE { v Code         }
  HasName      ::= SEQUENCE { v Name         }
  HasToken     ::= SEQUENCE { v Token        }
  HasVisi      ::= SEQUENCE { v Visi         }
  HasHex       ::= SEQUENCE { v HexDigit     }
  HasYesNo     ::= SEQUENCE { v YesNo        }
  HasVowels    ::= SEQUENCE { v Vowels       }
  HasUmlauts   ::= SEQUENCE { v Umlauts      }
  HasPair      ::= SEQUENCE { v Pair         }
  HasCaps      ::= SEQUENCE { v Caps         }
  HasQuad      ::= SEQUENCE { v Quad         }
  HasColor     ::= SEQUENCE { v Color        }
  HasShortList ::= SEQUENCE { v ShortList    }
  HasMidList   ::= SEQUENCE { v MidList      }
  HasByteCount ::= SEQUENCE { v ByteCount    }

  -- Inline SEQUENCE OF: elements checked against the element type
  HasNumList   ::= SEQUENCE { v SEQUENCE (SIZE(1..3)) OF NumericString }

  -- CHOICE: the active alternative checked against its own constraints,
  -- as a root, as a SEQUENCE member and as a SEQUENCE OF element
  PickAlt      ::= CHOICE {
    inl   [0] INTEGER (0..9),
    named [1] PercentInt,
    code  [2] NumericString (SIZE(2..3)),
    list  [3] SEQUENCE (SIZE(1..2)) OF PercentInt
  }
  HasPick      ::= SEQUENCE { v PickAlt }
  Picks        ::= SEQUENCE (SIZE(1..4)) OF PickAlt

END
