-- XER text layout (X.693 §8 BASIC-XER): whitespace between elements is not
-- significant, but the C++ and Rust encoders must write the same text as
-- asn1c byte for byte. A CHOICE as the document root is wrapped in its own
-- type name (X.693 §8.3.1); the closing tag follows the alternative's line.
XerLayoutTest DEFINITIONS AUTOMATIC TAGS ::= BEGIN

XlRoot ::= CHOICE {
    num     INTEGER,
    rec     SEQUENCE { a INTEGER, b BOOLEAN },
    sub     XlSub,
    list    SEQUENCE OF INTEGER,
    color   ENUMERATED { red, green },
    text    UTF8String
}

XlSub ::= CHOICE { x INTEGER, y BOOLEAN }

-- SEQUENCE OF CHOICE whose alternatives are constructed: each element is the
-- chosen alternative's own element (X.680 §25.5 Table 5, XMLValueList).
XlSeq ::= SEQUENCE {
    items   SEQUENCE OF XlItem,
    tail    INTEGER
}

XlItem ::= CHOICE {
    rec     SEQUENCE { a INTEGER },
    sub     XlSub,
    num     INTEGER,
    list    SEQUENCE OF INTEGER
}

END
