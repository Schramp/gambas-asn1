ChoiceTest DEFINITIONS ::= BEGIN
    HasAlt2 ::= SEQUENCE { val Alt2 }
    HasAlt4 ::= SEQUENCE { val Alt4 }
    Alt2 ::= CHOICE { num MyByte, flag BOOLEAN }
    -- 4 untagged alternatives, needs a non-involutory X.680 8.6 canonical
    -- reorder for the PER choice index (X.691 §22.2).
    Alt4 ::= CHOICE { num MyByte, str MyStr, flag BOOLEAN, raw OCTET STRING }
    MyByte ::= INTEGER (0..255)
    MyStr  ::= VisibleString (SIZE (1..8))
END
