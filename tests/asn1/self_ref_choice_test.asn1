SelfRefChoiceTest DEFINITIONS AUTOMATIC TAGS ::= BEGIN

    -- Direct recursive CHOICE: an alternative's type is the CHOICE itself
    -- (no SEQUENCE/OPTIONAL indirection to break the cycle). Mirrors
    -- tests/tests-asn1c-compiler/203-automatic-tags-OK.asn1's RecChoice.
    RecChoice ::= CHOICE {
        a INTEGER,
        b INTEGER,
        c RecChoice
    }

    -- Recursive SEQUENCE through an OPTIONAL member. AUTOMATIC TAGS makes
    -- `next` [1] IMPLICIT, so the cycle runs only through IMPLICIT-tagged
    -- members (no EXPLICIT wrapper, no CHOICE) in the BER decode.
    RecSeq ::= SEQUENCE {
        v    INTEGER,
        next RecSeq OPTIONAL
    }

END
