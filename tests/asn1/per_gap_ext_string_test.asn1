-- Extensible SIZE on known-multiplier character strings (X.691 §30.6:
-- one extension bit, then the root-constrained form when the length is
-- inside the root).
PerGapExtStringTest DEFINITIONS AUTOMATIC TAGS ::= BEGIN

Rec ::= SEQUENCE {
    ia5       IA5String (SIZE (1..8, ...)),
    printable PrintableString (SIZE (2..6, ...)),
    numeric   NumericString (SIZE (1..4, ...)),
    -- One extension marker over SIZE and FROM: the SIZE stays extensible,
    -- the FROM is not PER-visible (X.691 §9.3.9, §9.3.15).
    sizedFrom VisibleString (SIZE (1..8) INTERSECTION FROM ("a".."z"), ...)
}

END
