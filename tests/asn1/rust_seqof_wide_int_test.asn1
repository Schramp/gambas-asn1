-- Regression coverage: a SEQUENCE OF/SET OF element whose INTEGER
-- constraint picks wide (u64/i128) storage instead of the default i64
-- (X.680 semi-constrained non-negative, e.g. `INTEGER (0..MAX)`) must still
-- get a real encode/decode row, the same as a member-level wide INTEGER
-- already does (see rust_wide_types_test.asn1) — not fall back to
-- MemberAccess::Unsupported just because the element's native Rust type
-- isn't i64.

RustSeqOfWideIntTest DEFINITIONS ::= BEGIN

    WideIntList ::= SEQUENCE {
        counts SEQUENCE OF INTEGER (0..MAX)
    }

END
