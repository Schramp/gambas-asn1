-- Extensible SIZE on known-multiplier character strings (X.691 §26.4:
-- one extension bit, then the root-constrained form when the value is in
-- the extension root, otherwise the form without size or alphabet
-- constraint).
PerExtStringTest DEFINITIONS AUTOMATIC TAGS ::= BEGIN

Rec ::= SEQUENCE {
    ia5       IA5String (SIZE (1..8, ...)),
    printable PrintableString (SIZE (2..6, ...)),
    numeric   NumericString (SIZE (1..4, ...))
}

END
