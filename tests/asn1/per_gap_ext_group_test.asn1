-- SEQUENCE extension addition group [[ ]] (X.691 §19.9: a group is one
-- extension addition, encoded as an open type containing a SEQUENCE of
-- the group's components). asn1c also fails its own PER round trip on
-- this shape, so a mismatch here needs a hand check against X.691.
PerGapExtGroupTest DEFINITIONS AUTOMATIC TAGS ::= BEGIN

Rec ::= SEQUENCE {
    id        INTEGER (0..255),
    ...,
    [[
        g1    INTEGER (0..15),
        g2    BOOLEAN OPTIONAL
    ]]
}

END
