-- Extensible PermittedAlphabet (FROM (...), ...). X.691 §9.3.9: a FROM
-- with an extension marker is not PER-visible, so the effective alphabet
-- is the type's own (§9.3.10), and the marker adds no extension bit
-- (§9.3.15 note 1). Each member must encode exactly like the plain type:
-- 7-bit characters for VisibleString and IA5String in UNALIGNED.
-- asn1c instead writes 8-bit characters here (Schramp/asn1c#1), hence
-- skip-asn1c on this target.
PerExtFromTest DEFINITIONS AUTOMATIC TAGS ::= BEGIN

Rec ::= SEQUENCE {
    word      VisibleString (FROM ("a".."z"), ...),
    ia5       IA5String (FROM ("a".."z"), ...),
    -- One extension marker over SIZE and FROM: the SIZE stays extensible
    -- (extension bit), the FROM is not PER-visible (X.691 §9.3.9, §9.3.15).
    sizedFrom VisibleString (SIZE (1..8) INTERSECTION FROM ("a".."z"), ...)
}

END
