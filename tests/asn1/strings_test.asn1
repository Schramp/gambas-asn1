-- Minimal string type member tests.
-- Covers all ten new string types: NumericString through BmpString.

StringsTest DEFINITIONS ::= BEGIN

    HasNumericString   ::= SEQUENCE { value  NumericString }
    HasPrintableString ::= SEQUENCE { value  PrintableString }
    HasT61String       ::= SEQUENCE { value  T61String }
    HasVisibleString   ::= SEQUENCE { value  VisibleString }
    HasGeneralString   ::= SEQUENCE { value  GeneralString }
    HasGraphicString   ::= SEQUENCE { value  GraphicString }
    HasUniversalString ::= SEQUENCE { value  UniversalString }
    HasBmpString       ::= SEQUENCE { value  BMPString }
    HasVideotexString  ::= SEQUENCE { value  VideotexString }
    HasObjectDescriptor::= SEQUENCE { value  ObjectDescriptor }

    -- FROM-constrained string types: exercise PER alphabet encoding.
    -- Named types (not inline member constraints) so codegen emits a
    -- dedicated TypeDescriptor with constraints.alphabet populated.
    -- X.691 §26.5.7: canonical index = position in numerically-sorted alphabet.
    HexCharType   ::= IA5String      (FROM ("0"|"1"|"2"|"3"|"4"|"5"|"6"|"7"|"8"|"9"|"A"|"B"|"C"|"D"|"E"|"F"))
    YesNoCharType ::= IA5String      (FROM ("N"|"Y"))
    VowelType     ::= PrintableString (FROM ("a"|"e"|"i"|"o"|"u"))
    -- Declaration order differs from ASCII order: "F" "A" "9" "0" → sorted to {0x30 0x39 0x41 0x46}.
    -- Verifies Generator.cpp sorts alphabet before emitting and PerCodec encodes by sorted index.
    OutOfOrderType ::= IA5String     (FROM ("F"|"A"|"9"|"0"))

    HasHexStr     ::= SEQUENCE { value  HexCharType   }
    HasYesNoStr   ::= SEQUENCE { value  YesNoCharType }
    HasVowelStr   ::= SEQUENCE { value  VowelType     }
    HasOutOfOrder ::= SEQUENCE { value  OutOfOrderType }

    -- SIZE-only constraints on each built-in reduced string type.
    -- These inherit the builtin encode_table via builtin_alphabet_refs(); regression
    -- guard for the IA5String table fix (was sharing k_vis_enc, 95 chars, 0x20..0x7E).
    SizedIa5 ::= IA5String      (SIZE (1..10))
    SizedVis ::= VisibleString  (SIZE (1..10))
    SizedNum ::= NumericString  (SIZE (1..10))
    SizedPrt ::= PrintableString(SIZE (1..10))

    HasSizedIa5 ::= SEQUENCE { value  SizedIa5 }
    HasSizedVis ::= SEQUENCE { value  SizedVis }
    HasSizedNum ::= SEQUENCE { value  SizedNum }
    HasSizedPrt ::= SEQUENCE { value  SizedPrt }

END
