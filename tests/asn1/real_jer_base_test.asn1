-- JER-visible base constraints on REAL (X.697 §23.1.3, §23.1.4): when the
-- effective base constraint admits only 10, a base-10 value is a bare JSON
-- number; otherwise it is {"base10Value": n}. A base-2 value is a JSON
-- number in every case (§23.1.2).
RealJerBaseTest DEFINITIONS AUTOMATIC TAGS ::= BEGIN

Base10 ::= REAL (WITH COMPONENTS { ..., base (10) })
Base2  ::= REAL (WITH COMPONENTS { ..., base (2) })

Bases ::= SEQUENCE {
    b10    Base10,
    b2     Base2,
    inline REAL (WITH COMPONENTS { mantissa (-999999999999..999999999999), base (10), exponent (-20..20) }),
    x697   REAL (0 | WITH COMPONENTS { mantissa (-999999999999..999999999999), base (10), exponent (-20..20) }),
    both   REAL (WITH COMPONENTS { ..., base (2..10) }),
    plain  REAL
}

END
