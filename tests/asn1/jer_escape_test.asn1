-- JSON string escapes in JER input (RFC 8259 §7, X.697 §23.4 NOTE): every
-- JER string, member names included, may carry \uXXXX (with UTF-16
-- surrogate pairs), \b, \f, \n, \r, \t, \", \\ and \/. JeWide: BMPString and
-- UniversalString values are JSON strings of their characters (X.697 §38.1).
JerEscapeTest DEFINITIONS AUTOMATIC TAGS ::= BEGIN

JeRec ::= SEQUENCE {
    text UTF8String,
    alt  CHOICE { name UTF8String, n INTEGER }
}

JeWide ::= SEQUENCE {
    b BMPString,
    u UniversalString
}

END
