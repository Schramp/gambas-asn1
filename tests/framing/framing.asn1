-- Records for the BER framing vectors (tests/framing): definite-length
-- records with short and long-form lengths (X.690 §8.1.3.4, §8.1.3.5) and a
-- high tag number (X.690 §8.1.2.4). asn1c encodes them (records.vectors).
Framing DEFINITIONS AUTOMATIC TAGS ::= BEGIN

Rec ::= SEQUENCE {
    id   INTEGER,
    data OCTET STRING
}

High ::= [APPLICATION 300] IMPLICIT SEQUENCE {
    id   INTEGER
}

END
