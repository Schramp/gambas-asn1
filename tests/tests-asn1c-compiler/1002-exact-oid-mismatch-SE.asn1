-- SE: exact OID import must reject a module whose OID has extra version arcs.
-- VP::Exact uses oids_match (all arcs must be equal).
-- A prefix-only match (oids_match_descendants) would incorrectly accept this.

Importer
    { iso org(3) dod(6) internet(1) private(4) enterprise(1)
      spelio(9363) software(1) asn1c(5) test(1) 213 }
    DEFINITIONS ::=
BEGIN
    IMPORTS Foo FROM ExactTarget
        { iso org(3) dod(6) internet(1) private(4) enterprise(1)
          spelio(9363) software(1) asn1c(5) test(1) 212 };
    Bar ::= Foo
END


ExactTarget
    { iso org(3) dod(6) internet(1) private(4) enterprise(1)
      spelio(9363) software(1) asn1c(5) test(1) 212 r17(17) v0(0) }
    DEFINITIONS ::=
BEGIN
    Foo ::= INTEGER
END
