-- OK: Everything is fine

-- iso.org.dod.internet.private.enterprise (1.3.6.1.4.1)
-- .spelio.software.asn1c.test (9363.1.5.1)
-- .121

ModuleIMPORTS
	{ iso org(3) dod(6) internet (1) private(4) enterprise(1)
		spelio(9363) software(1) asn1c(5) test(1) 161 }
	DEFINITIONS AUTOMATIC TAGS ::=
BEGIN

	IMPORTS ImportedType
	FROM ImportedModule1 
	{ iso org(3) dod(6) internet (1) private(4) enterprise(1)
	  spelio(9363) software(1) asn1c(5) test(1) 163 major-version-1(1) }
	WITH DESCENDANTS
	;

	Type ::= ImportedType

END


ImportedModule1
	{ iso org(3) dod(6) internet (1) private(4) enterprise(1)
		spelio(9363) software(1) asn1c(5) test(1) 163 major-version-1(1) super-minor-version(1) super-minor-version(1)}
	DEFINITIONS AUTOMATIC TAGS ::=
BEGIN

	IMPORTS -- nothing --;

	ImportedType ::= INTEGER

END
