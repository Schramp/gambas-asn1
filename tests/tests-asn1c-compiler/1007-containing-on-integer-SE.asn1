-- X.682 §11.3: a contents constraint applies only to OCTET STRING and to
-- BIT STRING without a NamedBitList.

ModuleContainingOnInteger { iso org(3) dod(6) internet(1) private(4) enterprise(1) spelio(9363) software(1) asn1c(5) test(1) 1007 }
DEFINITIONS AUTOMATIC TAGS ::= BEGIN
    Local ::= SEQUENCE { x INTEGER }
    Flags ::= BIT STRING { a(0), b(1) } (CONTAINING Local)
    Bad ::= INTEGER (CONTAINING Local)
END
